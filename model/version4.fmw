FME workspace version4.fmw

Parameters:
- SourceDataset_OGCKML = C:\Users\sherr\Desktop\UTM\GEOINFORMATICS\SEM VIII\SBEG4664 UNDERGRADUATE PROJECT II\Models Store\model1.kmz   # Source Google KML File or URL
- SourceDataset_CSV2 = C:\Users\sherr\Desktop\UTM\GEOINFORMATICS\SEM VIII\SBEG4664 UNDERGRADUATE PROJECT II\databases\Mapping between 3D objects and tables.csv   # Source CSV (Comma Separated Value) File(s)
- DestDataset_CESIUM3DTILES = C:\Users\sherr\Desktop\UTM\GEOINFORMATICS\SEM VIII\SBEG4664 UNDERGRADUATE PROJECT II\Models Store\citygml\vers   # Destination Cesium 3D Tiles Folder

Readers:
- OGCKML_1: OGCKML from $(SourceDataset_OGCKML)
- CSV2_1: CSV2 from $(SourceDataset_CSV2)

Writers:
- CESIUM3DTILES_1: CESIUM3DTILES to $(DestDataset_CESIUM3DTILES)

Placemark (reader OGCKML_1)
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> FeatureMerger [REQUESTOR]
CSV (reader CSV2_1)
    attributes: _part_number uint32, model_id uint32, pid varchar(8), name varchar(34), party_type varchar(12), id_number uint64, address varchar(86), phone varchar(20), email varchar(14), group_name varchar(17), uid varchar(8), type varchar(6), status varchar(10), registration_date date, category varchar(9), ownership_type varchar(7), rrr_id varchar(24), rrr_type varchar(14), suid varchar(8), vertical_extent varchar(4)
    -> FeatureMerger [SUPPLIER]
FeatureMerger
    ATTR_ACCUM_MODE = Merge Supplier
    ATTR_CONFLICT_RES = Use Requestor
    IGNORE_NULLS = No
    JOIN_KEYS = @Value(_part_number) @Value(_part_number) AUTO
    MERGE_TYPE = Attributes Only
    PROCESS_DUPS = NO
    REJECT_NULL_MISSING_KEYS = No
    SUPPLIERS_FIRST = No
    MERGED -> AttributeRemover
AttributeRemover
    REMOVE_ATTRS = _geometry_name,_part_number
    -> tileset (writer CESIUM3DTILES_1)
tileset (writer CESIUM3DTILES_1)
    attributes: model_id int, pid string, name string, party_type string, id_number string, address string, phone string, email string, group_name string, uid string, type string, status string, registration_date string, category string, ownership_type string, rrr_id string, rrr_type string, suid string, vertical_extent string
